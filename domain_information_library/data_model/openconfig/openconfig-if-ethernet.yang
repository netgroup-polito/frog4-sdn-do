module openconfig-if-ethernet {

  yang-version "1";

  // namespace
  namespace "http://openconfig.net/yang/interfaces/ethernet";

  prefix "eth";

  // import some basic types
  import openconfig-interfaces { prefix ocif; }
  import iana-if-type { prefix ift; }
  import ietf-yang-types { prefix yang; }
  import openconfig-extensions { prefix oc-ext; }

  // meta
  organization "OpenConfig working group";

  contact
    "OpenConfig working group
    netopenconfig@googlegroups.com";

  description
    "Model for managing Ethernet interfaces -- augments the IETF YANG
    model for interfaces described by RFC 7223";

  revision "2015-10-09" {
    description
      "Initial OpenConfig public release";
    reference "0.1.1";
  }

  revision "2015-08-20" {
    description
      "Initial revision";
    reference "Pre-release";
  }
  
  oc-ext:openconfig-version "0.1.1";


  // extension statements

  // feature statements

  // identity statements

  identity ethernet-speed {
    description "base type to specify available Ethernet link
    speeds";
  }

  identity SPEED_10Mb {
    base ethernet-speed;
    description "10 Mbps Ethernet";
  }

  identity SPEED_100Mb {
    base ethernet-speed;
    description "100 Mbps Ethernet";
  }

  identity SPEED_1Gb {
    base ethernet-speed;
    description "1 Gbps Ethernet";
  }

  identity SPEED_10Gb {
    base ethernet-speed;
    description "10 Gbps Ethernet";
  }

  identity SPEED_25Gb {
    base ethernet-speed;
    description "25 Gbps Ethernet";
  }

  identity SPEED_40Gb {
    base ethernet-speed;
    description "40 Gbps Ethernet";
  }

  identity SPEED_50Gb {
    base ethernet-speed;
    description "50 Gbps Ethernet";
  }

  identity SPEED_100Gb {
    base ethernet-speed;
    description "100 Gbps Ethernet";
  }

  identity SPEED_UNKNOWN {
    base ethernet-speed;
    description
      "Interface speed is unknown.  Systems may report
      speed UNKNOWN when an interface is down or unpopuplated (e.g.,
      pluggable not present).";
  }

  // typedef statements


  // grouping statements

  grouping ethernet-interface-config {
    description "Configuration items for Ethernet interfaces";

    leaf mac-address {
      type yang:mac-address;
      description
        "Assigns a MAC address to the Ethernet interface.  If not
        specified, the corresponding operational state leaf is
        expected to show the system-assigned MAC address.";
    }

    leaf duplex-mode {
      type enumeration {
        enum AUTO {
          description "Auto-negotiated duplex mode";
        }
        enum FULL {
          description "Full duplex mode";
        }
        enum HALF {
          description "Half duplex mode";
        }
      }
      default AUTO;
      description "Set the duplex mode of the interface to full-
      or half-duplex operation.";
    }

    choice port-speed {
      description "Port speed can either be auto-negotiated or set
      explicitly";
      case auto {
        leaf auto {
          type empty;
          description "Set the link speed to auto-negotiate";
        }
      }
      case manual {
        leaf speed {
          type identityref {
            base ethernet-speed;
          }
          description "Set the link speed to a fixed value --
          supported values are defined by ethernet-speed
          identities";
        }
      }
    }

    leaf enable-flow-control {
      type boolean;
      default false;
      description
        "Enable or disable flow control for this interface.
        Ethernet flow control is a mechanism by which a receiver
        may send PAUSE frames to a sender to stop transmission for
        a specified time.";
      reference
        "IEEE 802.3x";
    }
  }

  grouping ethernet-interface-state-counters {
    description
      "Ethernet-specific counters and statistics";

    // ingress counters

    leaf in-mac-control-frames {
      type yang:counter64;
      description
        "MAC layer control frames received on the interface";
    }

    leaf in-mac-pause-frames {
      type yang:counter64;
      description
        "MAC layer PAUSE frames received on the interface";
    }

    leaf in-oversize-frames {
      type yang:counter64;
      description
        "Number of oversize frames received on the interface";
    }

    leaf in-jabber-frames {
      type yang:counter64;
      description
        "Number of jabber frames received on the
        interface.  Jabber frames are typically defined as oversize
        frames which also have a bad CRC.  Implementations may use
        slightly different definitions of what constitutes a jabber
        frame.  Often indicative of a NIC hardware problem.";
    }

    leaf in-fragment-frames {
      type yang:counter64;
      description
        "Number of fragment frames received on the interface.";
    }

    leaf in-8021q-frames {
      type yang:counter64;
      description
        "Number of 802.1q tagged frames received on the interface";
    }

    leaf in-crc-errors {
      type yang:counter64;
      description
        "Number of receive error events due to FCS/CRC check
        failure";
    }

    // egress counters

    leaf out-mac-control-frames {
      type yang:counter64;
      description
        "MAC layer control frames sent on the interface";
    }

    leaf out-mac-pause-frames {
      type yang:counter64;
      description
        "MAC layer PAUSE frames sent on the interface";
    }

    leaf out-8021q-frames {
      type yang:counter64;
      description
        "Number of 802.1q tagged frames sent on the interface";
    }
  }

  grouping ethernet-interface-state {
    description
      "Grouping for defining Ethernet-specific operational state";

    container counters {
      description "Ethernet interface counters";

      uses ethernet-interface-state-counters;

    }

  }

  // data definition statements

  grouping ethernet-top {
    description "top-level Ethernet config and state containers";

    container ethernet {
      description
        "Top-level container for ethernet configuration
        and state";

      container config {
        description "Configuration data for ethernet interfaces";

        uses ethernet-interface-config;

      }

      container state {

        config false;
        description "State variables for Ethernet interfaces";

        uses ethernet-interface-config;
        uses ethernet-interface-state;

      }

    }
  }

  // augment statements

  augment "/ocif:interfaces/ocif:interface" {
    when "ocif:type = 'ift:ethernetCsmacd'" {
      description "Additional interface configuration parameters when
      the interface type is Ethernet";
    }
    description "Adds addtional Ethernet-specific configuration to
    interfaces model";

    uses ethernet-top;
  }

  // rpc statements

  // notification statements

}
