// Contents of "netgroup-vlan"
module netgroup-vlan {
    namespace "urn:opendaylight:netgroup-vlan";
    prefix "netgroup-vlan";

    import netgroup-domain { prefix netgroup-domain; revision-date 2016-07-02; }
    import openconfig-vlan { prefix openconfig-vlan; }
    import iana-if-type { prefix iana-if-type; revision-date 2016-06-09; }
    import netgroup-if-ethernet { prefix netgroup-if-ethernet; revision-date 2016-07-05; }

    revision 2016-07-05 {
        description "Initial revision";
    }

    augment "/netgroup-domain:informations/netgroup-domain:hardware-informations/netgroup-domain:interfaces/netgroup-domain:interface" +
    "/netgroup-domain:subinterfaces/netgroup-domain:subinterface" {
    //TODO: augmentation path will need to be updated for
    //full device model
    description "Adds VLAN settings to individual subinterfaces";

    uses openconfig-vlan:vlan-logical-top;
  }

  augment "/netgroup-domain:informations/netgroup-domain:hardware-informations/netgroup-domain:interfaces/netgroup-domain:interface" +
  	"/netgroup-if-ethernet:ethernet" {
    //TODO: augmentation path will need to be updated for
    //full device model
    when "../netgroup-domain:config/netgroup-domain:type = 'iana-if-type:ethernetCsmacd'" {
      description "Active when the interface is Ethernet";
    }
    description "Adds VLAN settings to individual Ethernet
    interfaces";

    uses openconfig-vlan:vlan-top;
  }

  augment "/netgroup-domain:informations/netgroup-domain:hardware-informations/netgroup-domain:interfaces/netgroup-domain:interface" {
    when "netgroup-domain:type = 'iana-if-type:l3ipvlan'" {
      description
        "Active when the interface is a logical interface providing
        L3 routing for VLANs";
    }
    description
      "Adds configuration and state for routed VLAN interfaces";

    uses openconfig-vlan:vlan-routed-top;
  }
/*
  augment "/netgroup-domain:informations/netgroup-domain:hardware-informations/netgroup-domain:interfaces/netgroup-domain:interface" +
	"/netgroup-if-ethernet:ethernet/netgroup-vlan:vlans/vlan/config" {

	    description
	      "add interface mod";

	    leaf interface-mode {
	    	type enumeration {
	    		enum TRUNK;
	    		enum ACCESS;
	    	}
	    }
  }

  augment "/netgroup-domain:informations/netgroup-domain:hardware-informations/netgroup-domain:interfaces/netgroup-domain:interface" +
  	"/netgroup-if-ethernet:ethernet/netgroup-vlan:vlans/vlan/config" {
	    when "netgroup-vlan:interface-mode = 'TRUNK'";
	    description "trunk vlan";

	    leaf-list trunk-vlans {
	    	type uint16;
	    }
	}
*/
}
