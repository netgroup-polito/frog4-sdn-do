module netgroup-if-gre {
		
	namespace "https://github.com/netgroup-polito/yang/netgroup-if-gre";
	
	prefix "netgroup-if-gre";
	
	import ietf-inet-types { prefix inet; }
  	import netgroup-domain { prefix netgroup-domain; revision-date 2016-07-02; }
	
	grouping gre-top {
		list gre {
			key name;
			
			leaf name {
	        	type string;
	        	description 
	        		"Name of a gre port.";
	        }
			
	        container config {
	        	leaf unnumbered {
	        		type boolean;
	        		default false;
	        		description 
	        			"Indicates whether the subinterface is unnumbered, i.e.,
        				does not have an IP address assigned.";
	        	}
	        	
	        	leaf name {
	        		type string;
	        		description 
	        			"Name of a gre port.";
	        	}
	        	
	        	leaf description {
	        		type string;
	        		description 
	        			"Description of a gre port.";
	        	}
	        	
	        	leaf enabled {
	        		type boolean;
	        		default false;
	        		description
	        			"[adapted from IETF interfaces model (RFC 7223)]

						This leaf contains the configured, desired state of the
						interface.

						Systems that implement the IF-MIB use the value of this
						leaf in the 'running' datastore to set
						IF-MIB.ifAdminStatus to 'up' or 'down' after an ifEntry
						has been initialized, as described in RFC 2863.

						Changes in this leaf in the 'running' datastore are
						reflected in ifAdminStatus, but if ifAdminStatus is
						changed over SNMP, this leaf is not affected.";
      				reference
       	 				"RFC 2863: The Interfaces Group MIB - ifAdminStatus";
	        	}
	        }
	        
	        container state {
	        
	        	leaf admin-status {
			    	type enumeration {
						enum UP {
						  description
							"Ready to pass packets.";
						}
						enum DOWN {
						  description
							"Not ready to pass packets and not in some test mode.";
						}
						enum TESTING {
						  //TODO: This is generally not supported as a configured
						  //admin state, though it's in the standard interfaces MIB.
						  //Consider removing it.
						  description
							"In some test mode.";
						}
		  			}
		  		}
	        	
	        	leaf oper-status {
	        		type enumeration {
						enum UP {
						  value 1;
						  description
							"Ready to pass packets.";
						}
						enum DOWN {
						  value 2;
						  description
							"The interface does not pass any packets.";
						}
						enum TESTING {
						  value 3;
						  description
							"In some test mode.  No operational packets can
							 be passed.";
						}
						enum UNKNOWN {
						  value 4;
						  description
							"Status cannot be determined for some reason.";
						}
						enum DORMANT {
						  value 5;
						  description
							"Waiting for some external event.";
						}
						enum NOT-PRESENT {
						  value 6;
						  description
							"Some component (typically hardware) is missing.";
						}
						enum LOWER-LAYER-DOWN {
						  value 7;
						  description
							"Down due to state of lower-layer interface(s).";
						}
      				}
	        	}
	        }
	        
	        container options {
	        	leaf local_ip {
	        		type inet:ipv4-address-no-zone;
	        		description 
	        			"The tunnel destination IP that received packets must match";
	        	}
	        	
	        	leaf remote_ip {
	        		type inet:ipv4-address-no-zone;
	        		description 
	        			"The remote tunnel endpoint";
	        	}
	        	
	        	leaf in_key {
	        		type string;
	        		description 
	        			"The key that received packets must contain";
	        	}
	        	
	        	leaf out_key {
	        		type string;
	        		description 
	        			"The key to be set on outgoing packets";
	        	}
	        	
	        	leaf key {
	        		type string;
	        		description 
	        			"Shorthand to set in_key and out_key at the same time.";
	        	}
	        }
		}
	}
	
	augment "/netgroup-domain:informations/netgroup-domain:hardware-informations/netgroup-domain:interfaces/netgroup-domain:interface/" +
    "netgroup-domain:subinterfaces/netgroup-domain:subinterface" {
    	description "Gre ports currently presents on a subinterface.";
    	uses gre-top;
	}
	
	
}
